module o-ran-sc-ric-alarms-v1 {
  yang-version 1.1;
  namespace "urn:o-ran:ric:alarms:1.0";
  prefix osc-ric-al;

  import ietf-alarms {
    prefix al;
  }

  organization
    "O-RAN Software Community";
  contact
    "www.o-ran.org";
  description
    "This module defines the alarm identities for the O-RAN-SC Near realtime RAN Intelligent Controller.

     Copyright 2019 the O-RAN Alliance.

     Licensed under the Apache License, Version 2.0 (the 'License');
     you may not use this file except in compliance with the License.
     You may obtain a copy of the License at

      http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision 2020-03-08 {
    description
      "initial revision";
    reference
      "O-RAN-OAM-Interface-Specification (O1)";
  }

  identity alarm-type-id {
    base al:alarm-type-id;
    description
      "An abstract alarm type used for all O-RAN-SC specific alarm types for
       Managed Function Non-RT-RIC.";
  }

  identity e2-connection-loss {
    base alarm-type-id;
    description
      "Loss of E2 connection to E2 node.
       Instructions:
       Check if reconnect happened, e.g. using the health check in RIC-95.";
  }

  identity time-out {
    base alarm-type-id;
    description
      "Internal routing table update distribution might be incomplete
       due to time out.
       Instructions:
       Operator to check if there were any failures in any of the components
       involved (xApp restarts, for example)if no such failures, operator
       might have to update time out settings in the configuration to
       adjust RIC system to scheduling latencies of the underlying cloud
       platform.";
  }

  identity overload {
    base alarm-type-id;
    description
      "RIC messages could not be send or received due to temporary overload.
       Instructions:
       Operator to check for any failures. If no failures, operator might
       have to adjust buffer sizes and timeouts and/or scale out the system.";
  }
}
