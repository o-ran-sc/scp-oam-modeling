module o-ran-sc-ru-alarms-v1 {
  yang-version 1.1;
  namespace "urn:o-ran-sc:yang:o-ran-sc-ru-alarms-v1";
  prefix osc-ru-al;

  import ietf-alarms {
    prefix al;
  }

  organization
    "O-RAN Software Community";
  contact
    "www.o-ran-sc.org";
  description
    "This module defines the alarm identities for the O-RAN-SC Components.

     Copyright 2021 the O-RAN Software Community.

     Licensed under the Apache License, Version 2.0 (the 'License');
     you may not use this file except in compliance with the License.
     You may obtain a copy of the License at

      http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision 2021-03-09 {
    description
      "The namespace was updated according to O-RAN-SC yang guidelines.
       The namespace must end with the full module name.";
    reference
      "https://jira.o-ran-sc.org/browse/OAM-168";
  }
  revision 2020-01-18 {
    description
      "initial revision";
    reference
      "O-RAN-OAM-Interface-Specification (O1)";
  }

  identity alarm-type-id {
    base al:alarm-type-id;
    description
      "An abstract alarm type used for all O-RAN-SC specific alarm types for
       Managed Function O-RU.";
  }

  identity huston-we-have-a-problem {
    base alarm-type-id;
    description
      "A generic alarm which is under development and analysis,
       must not happen in production environment.
       Instructions:
         Create an JIRA issue and provide the following information:
         - SMO version, build number or git hash
         - O-RU version, build number or git hash
         - A procedure to reproduce the alarm.";
  }
}
