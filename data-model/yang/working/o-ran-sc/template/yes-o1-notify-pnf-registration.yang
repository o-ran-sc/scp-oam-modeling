module yes-o1-notify-pnf-registration {
  yang-version 1.1;
  namespace "urn:o-ran-sc:params:xml:ns:yang:yes-o1-notify-pnf-registration";
  prefix ypr;

  import yang-based-event-stream {
    prefix yes;
    reference
      "wiki.opnfv.org/display/ves/VES+goes+YES";
  }
  import yes-types {
    prefix yt;
    reference
      "wiki.opnfv.org/display/ves/VES+goes+YES";
  }
  import ietf-inet-types {
    prefix inet;
    reference
      "RFC 6991: YANG data types for Internet addresses and related
       things.";
  }
  import ietf-yang-types {
    prefix yang;
    reference
      "RFC 6991: Common YANG Data Types.";
  }

  organization
    "O-RAN Software Community";
  contact
    "www.o-ran-sc.org";
  description
    "This module is inspired by VES 7.1.1 but uses YANG concepts and types to
     describe the exchanged data format.
     The module yes-o1-notify-pnf-registration is only required, if the
     network function does not support NETCONF CALL HOME but RESTCONF
     asynchronous messages

     Due to the different hardware definitions by 3GPP and by IETF two
     additional and complimentary yang models are available. It is recommended
     that the NETCONF-Server offers an implementation at least of one of the
     following additional yang modules:

      - yes-o1-notify-pnf-registration-3gpp-hardware
      - yes-o1-notify-pnf-registration-ietf-hardware

     Copyright 2022 highstreet technologies GmbH and others.

     Licensed under the Apache License, Version 2.0 (the 'License');
     you may not use this file except in compliance with the License.
     You may obtain a copy of the License at

      http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision 2022-09-12 {
    description
      "Initial version;
       including feedback from WG4 about the usage of RFC 8348.";
    reference
      "ONAP SDN-R: wiki.onap.org/display/DW/SDN-R
       VES: wiki.opnfv.org/display/ves/VES+Home
            docs.onap.org/en/frankfurt/submodules/dcaegen2.git/docs/sections/services/ves-http
       YES: wiki.opnfv.org/display/ves/VES+goes+YES
       O-RAN Operations and Maintenance Interface Specification (O-RAN.WG10.O1-Interface.0-v07.00)
             section 2.7.2.4 Operations and Notifications
       RFC 8348: A YANG Data Model for Hardware Management";
  }

  /*
   * Identities
   */

  identity o1-notify-pnf-registration {
    base yt:domain-id;
    description
      "Indicates, that the event body contains o1-notify-nf-registration
       asynchronous message context.";
  }

  /*
   * Groupings
   */

  grouping o1-notify-pnf-registration-grp {
    leaf object-class {
      type string {
        length "3..255";
      }
      mandatory true;
      description
        "The name of the object class describing a PNF in the context of
         PNF registration. ";
    }
    leaf object-instance {
      type yt:resource;
      mandatory true;
      description
        "Reference to the object representing the PNF.";
    }
    leaf notification-identifier {
      type uint64;
      mandatory true;
      description
        "An notification identifier of this event as defined in ITU-T Rec. X.733.";
      reference
        "ITU-T Rec. X.733 - section 8.1.2.8.";
    }
    leaf notification-type {
      type yt:domain-id;
      mandatory true;
      description
        "Only the domain identity 'o1-notify-pnf-registration' is allowed.";
    }
    leaf event-time {
      type yang:date-and-time;
      mandatory true;
      description
        "The earliest time aka epoch time associated with the event from
         any component.";
    }
    leaf system-distinguished-name {
      type string;
      mandatory true;
      description
        "Distinguished Name of the management service provider of the notification";
    }
    leaf o1-specification-version {
      type string {
        length "1..5";
      }
      mandatory true;
      description
        "The version of the O1 Specification defining the format of this PNF registration notification";
    }
    choice vendor {
      case vendor-private-enterprise-number {
        leaf vendor-pen {
          type uint32;
          description
            "Network function vendor IANA private enterprise number.";
        }
      }
      description
        "The network function vendor can be identified by its name or by its
         IANA private enterprise number (PEN)";
      reference
        "IANA Private Enterprise Numbers
          http://www.iana.org/assignments/enterprise-numbers/enterprise-numbers";
    }
    leaf oam-host {
      type inet:host;
      mandatory true;
      description
        "The m-plane fully qualified domain name (host) or IP address to
         be used by the manager to contact the PNF.";
      reference
        "O-RAN Operations and Maintenance Interface Specification (O-RAN.WG10.O1-Interface.0-v07.00)
           section 2.7.2.4 Operations and Notifications - oamV4IpAddress and oamV6IpAddress";
    }
    leaf oam-port {
      type inet:port-number;
      default "830";
      description
        "The port number the PNF listens for OAM commands..";
    }
    leaf unit-family {
      type string {
        length "1..255";
      }
      description
        "The general type of hardware.";
      reference
        "3GPP TS 28.632 vendorUnitFamilyType";
    }
    leaf unit-type {
      type string {
        length "1..255";
      }
      description
        "Vendor name for the network function";
      reference
        "3GPP TS 28.632 vendorUnitTypeNumber";
    }
    leaf restart-reason {
      type string {
        length "1..255";
      }
      description
        "The reason the network function restarted.";
    }
    description
      "An object class containing o1-notify-pnf-registration specific parameters.";
  }

  /*
   * Augmentation of YES
   */

  augment "/yes:event-history/yes:event" {
    when "derived-from-or-self(/yes:event-history/yes:event/yes:header/yes:domain, 'ypr:o1-notify-pnf-registration')" {
      description
        "The event header must indicate 'o1-notify-pnf-registration'.";
    }
    if-feature "yes:event-history";
    container o1-notify-pnf-registration {
      uses o1-notify-pnf-registration-grp;
      description
        "A single object for specific parameters, used for the registration of
         physical network functions (PNF).";
    }
    description
      "Adds to YES the specifics of o1-notify-pnf-registration notifications.";
  }

  augment "/yes:yang-based-event-stream/yes:event" {
    when "derived-from-or-self(/yes:yang-based-event-stream/yes:event/yes:header/yes:domain, 'ypr:o1-notify-pnf-registration')" {
      description
        "The event header must indicate 'o1-notify-pnf-registration'.";
    }
    container o1-notify-pnf-registration {
      uses o1-notify-pnf-registration-grp;
      description
        "A single object for specific parameters, used for the registration of
         physical network functions (PNF).";
    }
    description
      "Adds to YES the specifics of o1-notify-pnf-registration notifications.";
  }
}
