module o-ran-qos{
  yang-version 1.1;
  namespace "urn:o-ran:qos:1.0";
  prefix "o-ran-du-qos";
    
  import _3gpp-common-managed-element {
    prefix "me3gpp";
  }

  import _3gpp-nr-nrm-gnbdufunction {
    prefix "gnbdu3gpp";
  }
  
  import ietf-hardware {
    prefix hw;
  }
  
  import o-ran-hardware {
    prefix o-ran-hw;
    revision-date "2020-04-17";
  }
  
  organization 
  "O-RAN Alliance";

contact
  "www.o-ran.org";

description 
  "This module defines the YANG definitions for QoS configuration for O-DU. 
   This is used to augment SA5 DU data model.

   Copyright 2020 the O-RAN Alliance.

   THIS SOFTWARE IS PROVIDED BY THE COPYRIGHT HOLDERS AND CONTRIBUTORS 'AS IS'
   AND ANY EXPRESS OR IMPLIED WARRANTIES, INCLUDING, BUT NOT LIMITED TO, THE
   IMPLIED WARRANTIES OF MERCHANTABILITY AND FITNESS FOR A PARTICULAR PURPOSE
   ARE DISCLAIMED. IN NO EVENT SHALL THE COPYRIGHT HOLDER OR CONTRIBUTORS BE
   LIABLE FOR ANY DIRECT, INDIRECT, INCIDENTAL, SPECIAL, EXEMPLARY, OR
   CONSEQUENTIAL DAMAGES (INCLUDING, BUT NOT LIMITED TO, PROCUREMENT OF
   SUBSTITUTE GOODS OR SERVICES; LOSS OF USE, DATA, OR PROFITS; OR BUSINESS
   INTERRUPTION) HOWEVER CAUSED AND ON ANY THEORY OF LIABILITY, WHETHER IN
   CONTRACT, STRICT LIABILITY, OR TORT (INCLUDING NEGLIGENCE OR OTHERWISE)
   ARISING IN ANY WAY OUT OF THE USE OF THIS SOFTWARE, EVEN IF ADVISED OF THE
   POSSIBILITY OF SUCH DAMAGE.

   Redistribution and use in source and binary forms, with or without
   modification, are permitted provided that the following conditions are met:

   * Redistributions of source code must retain the above copyright notice,
     this list of conditions and the above disclaimer.
   * Redistributions in binary form must reproduce the above copyright notice,
     this list of conditions and the above disclaimer in the documentation
     and/or other materials provided with the distribution.
   * Neither the Members of the o-RAN Alliance nor the names of its
     contributors may be used to endorse or promote products derived from
     this software without specific prior written permission.";

  revision "2020-09-25" {
    description 
      "version 1.0.0 - first release of O-RAN O1 for O-DU YANG models";

    reference "ORAN-WG5.MP.0-v01.00";
  }
  
  grouping qos-config-group {
    list qos-config-group {
      key "qci";
      min-elements 1;
      leaf qci {
        type uint8 {
          range "0..255";
        }
        mandatory true;
        description "QoS Class Identifier defined in TS 23.401";
      }
      leaf qos-group-index {
        type uint8 {
          range "1..32";
        }
        mandatory true;
        description "QoS group index for the QCI";
      }
      description "List of QoS group index to QCI mapping";
    }      
    description "grouping for QoS configuration";
  }
  
  augment "/me3gpp:ManagedElement/gnbdu3gpp:GNBDUFunction/gnbdu3gpp:attributes" {
    when "(derived-from-or-self(/hw:hardware/hw:component/hw:class, 'o-ran-hw:O-DU-COMPONENT'))";
    uses qos-config-group;  
    description "SA5 gNB DU function augmented with QoS configuration";
  }
}
