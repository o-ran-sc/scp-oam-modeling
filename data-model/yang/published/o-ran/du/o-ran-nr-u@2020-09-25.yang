module o-ran-nr-u{
  yang-version 1.1;
  namespace "urn:o-ran:nr-u:1.0";
  prefix "o-ran-nr-u";
  
  import _3gpp-common-managed-element {
    prefix "me3gpp";
  }

  import _3gpp-nr-nrm-gnbdufunction {
    prefix "gnbdu3gpp";
  }
  
  import _3gpp-nr-nrm-nrcelldu {
    prefix "nrcelldu3gpp";
  }
  
  import ietf-hardware {
    prefix hw;
  }
  
  import o-ran-hardware {
    prefix o-ran-hw;
    revision-date "2020-04-17";
  }
  
  import o-ran_3gpp-nr-nrm-nrcelldu {
    prefix "or-nrcelldu";
  }
  
  organization 
  "O-RAN Alliance";

contact
  "www.o-ran.org";

description 
  "This module defines the YANG definitions for NR-U configuration. This is used
   to augment SA5 DU data model.

   Copyright 2020 the O-RAN Alliance.

   THIS SOFTWARE IS PROVIDED BY THE COPYRIGHT HOLDERS AND CONTRIBUTORS 'AS IS'
   AND ANY EXPRESS OR IMPLIED WARRANTIES, INCLUDING, BUT NOT LIMITED TO, THE
   IMPLIED WARRANTIES OF MERCHANTABILITY AND FITNESS FOR A PARTICULAR PURPOSE
   ARE DISCLAIMED. IN NO EVENT SHALL THE COPYRIGHT HOLDER OR CONTRIBUTORS BE
   LIABLE FOR ANY DIRECT, INDIRECT, INCIDENTAL, SPECIAL, EXEMPLARY, OR
   CONSEQUENTIAL DAMAGES (INCLUDING, BUT NOT LIMITED TO, PROCUREMENT OF
   SUBSTITUTE GOODS OR SERVICES; LOSS OF USE, DATA, OR PROFITS; OR BUSINESS
   INTERRUPTION) HOWEVER CAUSED AND ON ANY THEORY OF LIABILITY, WHETHER IN
   CONTRACT, STRICT LIABILITY, OR TORT (INCLUDING NEGLIGENCE OR OTHERWISE)
   ARISING IN ANY WAY OUT OF THE USE OF THIS SOFTWARE, EVEN IF ADVISED OF THE
   POSSIBILITY OF SUCH DAMAGE.

   Redistribution and use in source and binary forms, with or without
   modification, are permitted provided that the following conditions are met:

   * Redistributions of source code must retain the above copyright notice,
     this list of conditions and the above disclaimer.
   * Redistributions in binary form must reproduce the above copyright notice,
     this list of conditions and the above disclaimer in the documentation
     and/or other materials provided with the distribution.
   * Neither the Members of the o-RAN Alliance nor the names of its
     contributors may be used to endorse or promote products derived from
     this software without specific prior written permission.";

  revision "2020-09-25" {
    description 
      "version 1.0.0 - first release of O-RAN O1 for O-DU YANG models";

    reference "ORAN-WG5.MP.0-v01.00";
  }
  
  grouping nr-u-configuration-group {
    container assistance-information-data-list {
      container radio-quality-assistance-info {
        leaf average-cqi {
          type enumeration {
            enum DISABLE {
              description "Disable";
            }
            enum ENABLE {
              description "Enable";
            }
          }
          mandatory true;
          description 
            "Indicates whether gNB-DU shall include Average CQI information 
             when sending Assistance Information Data";
        
        }
        leaf average-harq-failure {
          type enumeration {
            enum DISABLE {
              description "Disable";
            }
            enum ENABLE {
              description "Enable";
            }
          }
          mandatory true;
          description 
            "Indicates whether gNB-DU shall include Average HARQ Failure 
             information when sending Assistance Information Data ";
        }
        leaf average-harq-retx {
          type enumeration {
            enum DISABLE {
              description "Disable";
            }
            enum ENABLE {
              description "Enable";
            }
          }
          mandatory true;
          description 
            "Indicates whether gNB-DU shall include Average HARQ Retransmissions 
             information when sending Assistance Information Data";
        }
        leaf dl-radio-quality-index {
          type enumeration {
            enum DISABLE {
              description "Disable";
            }
            enum ENABLE {
              description "Enable";
            }
          }
          mandatory true;
          description 
            "Indicates whether gNB-DU shall include DL Radio Quality Index information 
             when sending Assistance Information Data";
        }
        leaf ul-radio-quality-index {
          type enumeration {
            enum DISABLE {
              description "Disable";
            }
            enum ENABLE {
              description "Enable";
            }
          }
          mandatory true;
          description 
            "Indicates whether gNB-DU shall include UL Radio Quality Index information 
             when sending Assistance Information Data";
        }
        leaf power-headroom-report {
          type enumeration {
            enum DISABLE {
              description "Disable";
            }
            enum ENABLE {
              description "Enable";
            }
          }
          mandatory true;
          description 
            "Indicates whether gNB-DU shall include Power Headroom Report information 
             when sending Assistance Information Data [14].";
        }     
        description "container for radio-quality-assistance-info";
      }
      description "assistance-information-data-list";
    }
    description "grouping of NR-U configuration";
  }
  
  augment "/me3gpp:ManagedElement/gnbdu3gpp:GNBDUFunction/nrcelldu3gpp:NRCellDU/nrcelldu3gpp:attributes/or-nrcelldu:o-ran-configuration" {
    when "(derived-from-or-self(/hw:hardware/hw:component/hw:class, 'o-ran-hw:O-DU-COMPONENT'))";
    uses nr-u-configuration-group;
    description "SA5 gNB DU cell o-ran-container augmented with NR-U configuration";
  }
}
