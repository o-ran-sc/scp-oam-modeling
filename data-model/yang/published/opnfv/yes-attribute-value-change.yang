module yes-attribute-value-change {
    yang-version 1.1;
    namespace "urn:opnfv:params:xml:ns:yang:attribute-value-change";
    prefix yavc;

    import yang-based-event-stream {
        prefix yes;
        reference
          "wiki.opnfv.org/display/ves/VES+goes+YES";
    }
    import yes-types {
        prefix yt;
        reference
          "wiki.opnfv.org/display/ves/VES+goes+YES";
    }

    organization
      "Open Platform for NFV (OPNFV) - Virtual Event Streaming (VES) project";
    contact
      "wiki.opnfv.org/display/ves";
    description
      "This module contains a collection of YANG definitions for sending an
       attribute value change notification.

       Copyright 2020 highstreet technologies GmbH and others.

       Licensed under the Apache License, Version 2.0 (the 'License');
       you may not use this file except in compliance with the License.
       You may obtain a copy of the License at

        http://www.apache.org/licenses/LICENSE-2.0

       Unless required by applicable law or agreed to in writing, software
       distributed under the License is distributed on an 'AS IS' BASIS,
       WITHOUT WARRANTIES OR CONDITIONS OF ANY KIND, either express or implied.
       See the License for the specific language governing permissions and
       limitations under the License.";

    revision 2020-07-04 {
        description
          "Initial version";
        reference
          "ONAP SDN-R: wiki.onap.org/display/DW/SDN-R
           VES: wiki.opnfv.org/display/ves/VES+Home
                docs.onap.org/en/frankfurt/submodules/dcaegen2.git/docs/sections/services/ves-http
           YES: wiki.opnfv.org/display/ves/VES+goes+YES";
    }

    /*
     * Groupings
     */
    grouping attribute-value-change-grp {
        leaf object-reference {
            type instance-identifier {
                require-instance false;
            }
            mandatory true;
            description
              "A reference to the object containing the attribute (leaf).";
        }
        container schema {
            uses yt:schema-grp;
            description
              "The YANG module, which defines the type of the attribute
               identified by its namespace.";
        }
        anydata new-value {
            description
              "The new value which should be use on client datastores.
               It must be ensured that the value is defined by a yang module.
               if the new value is not delivered the manager (NMS;
               SDN-Controller, SMO, MnS, ...) must send a GET of GET-CONFIG
               request to the API provider. ";
        }
        anydata old-value {
            description
              "The new value which should be use on client datastores.
               It must be ensured that the value is defined by a yang module.";
        }
        description
          "An object class containing pnf-registration specific parameters.";
    }

    /*
     * Augmentation of YES
     */
    augment "/yes:event-history/yes:event" {
        when "derived-from-or-self(/yes:event-history/yes:event/yes:header/yes:domain, 'yavc:attribute-value-change')" {
            description
              "The event header must indicate 'attribute-value-change'.";
        }
        if-feature yes:event-history;
        list attribute-value-change {
            uses attribute-value-change-grp;
            description
              "A single object for specific parameters, used for the any change
               of value change.";
        }
        description
          "Adds to YES the specifics of attribute-value-change notifications.";
    }

    augment "/yes:yang-based-event-stream/yes:event" {
        when "derived-from-or-self(/yes:yang-based-event-stream/yes:event/yes:header/yes:domain, 'yavc:attribute-value-change')" {
            description
              "The event header must indicate 'attribute-value-change'.";
        }
        list attribute-value-change {
            uses attribute-value-change-grp;
            description
              "A single object for specific parameters, used for the any change
               of value change.";
        }
        description
          "Adds to YES the specifics of attribute-value-change notifications.";
    }
}
